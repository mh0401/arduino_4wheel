Gui.activateWorkbench("ArchWorkbench")
Gui.activateWorkbench("AssemblyWorkbench")
Gui.activateWorkbench("CompleteWorkbench")
App.newDocument()
App.setActiveDocument("Unnamed")
App.ActiveDocument=App.getDocument("Unnamed")
Gui.ActiveDocument=Gui.getDocument("Unnamed")
Gui.activateWorkbench("PartDesignWorkbench")
Gui.activateWorkbench("SketcherWorkbench")
Gui.activateWorkbench("PartDesignWorkbench")
App.activeDocument().addObject('Sketcher::SketchObject','Sketch')
App.activeDocument().Sketch.Placement = App.Placement(App.Vector(0.000000,0.000000,0.000000),App.Rotation(0.000000,0.000000,0.000000,1.000000))
Gui.activeDocument().activeView().setCamera('#Inventor V2.1 ascii \n OrthographicCamera {\n viewportMapping ADJUST_CAMERA \n position 0 0 87 \n orientation 0 0 1  0 \n nearDistance -112.88701 \n farDistance 287.28702 \n aspectRatio 1 \n focalDistance 87 \n height 143.52005 }')
Gui.activeDocument().setEdit('Sketch')
App.ActiveDocument.Sketch.addGeometry(Part.Line(App.Vector(-61.697960,10.101002,0),App.Vector(-62.243950,-51.050957,0)))
App.ActiveDocument.recompute()
App.ActiveDocument.Sketch.addConstraint(Sketcher.Constraint('Vertical',0)) 
App.ActiveDocument.recompute()
App.ActiveDocument.recompute()
App.ActiveDocument.Sketch.delGeometry(0)
App.ActiveDocument.Sketch.addGeometry(Part.Line(App.Vector(-100.259747,9.239660,0),App.Vector(80.416039,9.239660,0)))
App.ActiveDocument.Sketch.addGeometry(Part.Line(App.Vector(80.416039,9.239660,0),App.Vector(80.416039,-39.844796,0)))
App.ActiveDocument.Sketch.addGeometry(Part.Line(App.Vector(80.416039,-39.844796,0),App.Vector(-100.259747,-39.844796,0)))
App.ActiveDocument.Sketch.addGeometry(Part.Line(App.Vector(-100.259747,-39.844796,0),App.Vector(-100.259747,9.239660,0)))
App.ActiveDocument.Sketch.addConstraint(Sketcher.Constraint('Coincident',0,2,1,1)) 
App.ActiveDocument.Sketch.addConstraint(Sketcher.Constraint('Coincident',1,2,2,1)) 
App.ActiveDocument.Sketch.addConstraint(Sketcher.Constraint('Coincident',2,2,3,1)) 
App.ActiveDocument.Sketch.addConstraint(Sketcher.Constraint('Coincident',3,2,0,1)) 
App.ActiveDocument.Sketch.addConstraint(Sketcher.Constraint('Horizontal',0)) 
App.ActiveDocument.Sketch.addConstraint(Sketcher.Constraint('Horizontal',2)) 
App.ActiveDocument.Sketch.addConstraint(Sketcher.Constraint('Vertical',1)) 
App.ActiveDocument.Sketch.addConstraint(Sketcher.Constraint('Vertical',3)) 
App.ActiveDocument.recompute()
Gui.activeDocument().resetEdit()
App.ActiveDocument.recompute()
App.activeDocument().addObject("PartDesign::Pad","Pad")
App.activeDocument().Pad.Sketch = App.activeDocument().Sketch
App.activeDocument().Pad.Length = 10.0
App.ActiveDocument.recompute()
Gui.activeDocument().hide("Sketch")
Gui.activeDocument().setEdit('Pad')
App.ActiveDocument.Pad.Length = 35.000000
App.ActiveDocument.Pad.Reversed = 0
App.ActiveDocument.Pad.Midplane = 0
App.ActiveDocument.Pad.Length2 = 100.000000
App.ActiveDocument.Pad.Type = 0
App.ActiveDocument.Pad.UpToFace = None
App.ActiveDocument.recompute()
Gui.activeDocument().resetEdit()
App.ActiveDocument.addObject("Part::Box","Box")
App.ActiveDocument.recompute()
Gui.SendMsgToActiveView("ViewFit")
Gui.ActiveDocument.setEdit('Box',0)
Gui.getDocument("Unnamed").getObject("Box").ShapeColor=(0.30,0.90,0.91)
App.activeDocument().addObject('Sketcher::SketchObject','Sketch001')
App.activeDocument().Sketch001.Placement = App.Placement(App.Vector(0.000000,0.000000,0.000000),App.Rotation(0.000000,0.000000,0.000000,1.000000))
Gui.activeDocument().activeView().setCamera('#Inventor V2.1 ascii \n OrthographicCamera {\n viewportMapping ADJUST_CAMERA \n position 0 0 87 \n orientation 0 0 1  0 \n nearDistance -112.88701 \n farDistance 287.28702 \n aspectRatio 1 \n focalDistance 87 \n height 143.52005 }')
Gui.activeDocument().setEdit('Sketch001')
App.ActiveDocument.Sketch001.addGeometry(Part.Circle(App.Vector(-29.911188,59.688244,0),App.Vector(0,0,1),9.105104))
App.ActiveDocument.recompute()
Gui.getDocument('Unnamed').resetEdit()
App.getDocument('Unnamed').recompute()
App.activeDocument().addObject("PartDesign::Pad","Pad001")
App.activeDocument().Pad001.Sketch = App.activeDocument().Sketch001
App.activeDocument().Pad001.Length = 10.0
App.ActiveDocument.recompute()
Gui.activeDocument().hide("Sketch001")
Gui.activeDocument().setEdit('Pad001')
App.ActiveDocument.Pad001.Length = 10.000000
App.ActiveDocument.Pad001.Reversed = 0
App.ActiveDocument.Pad001.Midplane = 0
App.ActiveDocument.Pad001.Length2 = 100.000000
App.ActiveDocument.Pad001.Type = 0
App.ActiveDocument.Pad001.UpToFace = None
App.ActiveDocument.recompute()
Gui.activeDocument().resetEdit()
App.activeDocument().Sketch001.Support = (App.ActiveDocument.Pad,["Face6"])
App.activeDocument().recompute()
Gui.activeDocument().setEdit('Sketch001')
App.ActiveDocument.Sketch001.movePoint(0,0,App.Vector(-26.817975,50.454534,0),0)
App.ActiveDocument.recompute()
App.ActiveDocument.Sketch001.movePoint(0,0,App.Vector(-30.543518,44.347799,0),0)
App.ActiveDocument.recompute()
App.ActiveDocument.Sketch001.movePoint(0,0,App.Vector(-22.612050,55.395492,0),0)
App.ActiveDocument.recompute()
App.ActiveDocument.Sketch001.movePoint(0,3,App.Vector(-15.485100,-15.342569,0),0)
App.ActiveDocument.recompute()
Gui.getDocument('Unnamed').resetEdit()
App.getDocument('Unnamed').recompute()
App.getDocument("Unnamed").removeObject("Box")
print dir(App)
